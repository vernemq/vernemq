EXOMETER-METRICS-MIB DEFINITIONS ::= BEGIN

IMPORTS
    MODULE-IDENTITY, OBJECT-TYPE, NOTIFICATION-TYPE, Counter32, Counter64, Gauge32, Integer32, snmpModules, experimental FROM SNMPv2-SMI
    MODULE-COMPLIANCE, OBJECT-GROUP, NOTIFICATION-GROUP FROM SNMPv2-CONF;

exometerMetricsMIB MODULE-IDENTITY
    LAST-UPDATED "201401190525Z"
    ORGANIZATION "Feuerlabs"
    CONTACT-INFO "TODO" 
    DESCRIPTION 
        "This MIB module is used for exposing dynamic exometer metrics."
    REVISION  "201401190525Z"
    DESCRIPTION 
        "The initial version"
    ::= { snmpModules 1 }

exometerMetrics OBJECT IDENTIFIER ::= { experimental 7 }

-- CONTENT START

-- CONTENT END

END
